package ReleaseDefaults {
  action def Action;
  state def State;
  constraint def Constraint;
  requirement def Requirement;
  calc def Calculation;
  case def Case;
  use case def UseCase;
  verification def Verification;
  analysis def Analysis;
  flow def Flow;
  metadata def Metadata;
  occurrence def Occurrence;
}
