package ReleaseKernelDefaults {
    class Object;
    struct Structure;
    behavior Behavior;
    datatype Data;
    function Function;
    predicate Predicate;
    assoc Association;
    interaction Interaction;
    metaclass Metadata;
}
