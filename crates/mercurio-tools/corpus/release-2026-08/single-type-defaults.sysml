package ReleaseSingleTypeDefaults {
    calc calculation;
    constraint constraintCheck;
    assert constraint asserted { true }
    requirement requirementCheck;
    concern concernCheck;
    analysis analysisCheck;
    verification verificationCheck;
    use case useCheck;
    rendering renderingCheck;
    viewpoint viewpointCheck;
    view viewCheck;
}
